FME workspace KV.fmw

Parameters:
- GML_INPUT_FILE = /Users/ralph/Workspaces/geoxplore.nl/VectorKlic/work/GI_gebiedsinformatielevering_20O002737_1.xml   # GI_gebiedsinformatielevering.xml
- DGN_DEST_DIR = /Users/ralph/Workspaces/geoxplore.nl/VectorKlic/work/20O002737-out   # DGN Destination (Directory)
- DXF_DEST_DIR = /Users/ralph/Workspaces/geoxplore.nl/VectorKlic/work/20O002737-out   # DXF Destination (Directory)
- GML_INPUT_FILE_3 = /Users/ralph/Workspaces/geoxplore.nl/VectorKlic/work/GI_gebiedsinformatielevering_20O002737_1.xml   # Source Geography Markup Language (GML) File(s)

Readers:
- GML_1: GML from $(GML_INPUT_FILE)
- GML_2: GML from $(GML_INPUT_FILE_3)

Writers:
- ACAD_1: ACAD to $(DXF_DEST_DIR)
- DGNV8_1: DGNV8 to $(DGN_DEST_DIR)
- ACAD_2: ACAD to $(DXF_DEST_DIR)
- NULL_1: NULL

AttributeCreator__inspire_thema_id
    ATTR_TABLE = SET_TO inspire_thema_id = @Value(gml_id)
    -> FeatureJoiner [RIGHT]
FeatureJoiner
    ATTR_CONFLICT_RES = Use Left
    GEOMETRY_HANDLING = Use Left
    JOIN_KEYS = inNetwork{0}.xlink_href inspire_thema_id AUTO
    JOIN_MODE = Inner
    JOINED -> AttributeSplitter
    <REJECTED> -> NULL (writer NULL_1)
AttributeSplitter
    ATTR_NAME = thema.xlink_href
    DELIMITER = /
    DROP_EMPTY_PARTS = No
    LIST_NAME = _thema
    TRIM_OPTION = Both
    -> AttributeCreator
AttributeCreator
    ATTR_TABLE:
      SET_TO thema = @Value(_thema{7})
      SET_TO netbeheerder = @Value(inNetwork{0}.xlink_href)
      SET_TO layerName = LG_@Value(_thema{7})_@Value(inspire_thema_id)
    -> AttributeValueMapper
AttributeValueMapper
    DEFAULT_VALUE = #000000
    DIRECTION = Forward (Source To Destination)
    LUT = datatransport,0,1,0,gasLageDruk,1,0.84,0.31,gasHogeDruk,1,0.686,0.23,buisleidingGevaarlijkeInhoud,1,0.5,0,landelijkHoogspanningsnet,1,0,0,hoogspanning,1,0,0,middenspanning,0.784,0,0,laagspanning,0.588,0,0,petrochemie,1.41,0.29,0,rioolVrijVerval,0.73,0.22,0.66,rioolOnderDruk,0.5,0,0.5,rioolOnderOverOfOnderdruk,0.5,0,0.5,warmte,0.5,0,0.5,water,0,0,1,wees,0,0,0,overig,0,0,0
    SRC = thema
    VAL_ATTR = thema_color
    -> FeatureColorSetter
FeatureColorSetter
    COLOR = @Value(thema_color)
    FILL_COLOR = @Value(thema_color)
    MODE = Fixed
    COLORED -> UtilityLink (writer DGNV8_1)
    COLORED -> UtilityLink (writer ACAD_2)
    COLORED -> Layer1 (writer ACAD_1)
    <REJECTED> -> NULL (writer NULL_1)
NULL (writer NULL_1)
    attributes: inspireId.Identifier.localId char(255), inNetwork{}.xlink_href char(255), endNode.gml_remoteSchema char(255), startNode.gml_remoteSchema char(255), gml_parent_id char(255), gml_parent_property char(255), gml_id char(255)

Bookmark: XML Reader
UtilityLink (reader GML_1)
    attributes: beginLifespanVersion xml_datetime, beginLifespanVersion.nilReason xml_buffer, beginLifespanVersion.xsi_nil xml_boolean, inspireId.Identifier.localId xml_buffer, inspireId.Identifier.namespace xml_buffer, inspireId.Identifier.versionId xml_buffer, inspireId.Identifier.versionId.nilReason xml_buffer, inspireId.Identifier.versionId.xsi_nil xml_boolean, endLifespanVersion xml_datetime, endLifespanVersion.nilReason xml_buffer, endLifespanVersion.xsi_nil xml_boolean, inNetwork{}.owns xml_boolean, inNetwork{}.nilReason xml_buffer, inNetwork{}.gml_remoteSchema xml_buffer, inNetwork{}.xlink_href xml_buffer, inNetwork{}.xlink_role xml_buffer, inNetwork{}.xlink_title xml_buffer, inNetwork{}.xsi_nil xml_boolean, centrelineGeometry xml_geometry, fictitious xml_boolean, endNode.owns xml_boolean, endNode.nilReason xml_buffer, endNode.gml_remoteSchema xml_buffer, endNode.xlink_href xml_buffer, endNode.xlink_role xml_buffer, endNode.xlink_title xml_buffer, startNode.owns xml_boolean, startNode.nilReason xml_buffer, startNode.gml_remoteSchema xml_buffer, startNode.xlink_href xml_buffer,
      startNode.xlink_role xml_buffer, startNode.xlink_title xml_buffer, currentStatus.owns xml_boolean, currentStatus.nilReason xml_buffer, currentStatus.gml_remoteSchema xml_buffer, currentStatus.xlink_href xml_buffer, currentStatus.xlink_role xml_buffer, currentStatus.xlink_title xml_buffer, currentStatus.xsi_nil xml_boolean, validFrom xml_datetime, validFrom.nilReason xml_buffer, validFrom.xsi_nil xml_boolean, validTo xml_datetime, validTo.nilReason xml_buffer, validTo.xsi_nil xml_boolean, verticalPosition xml_char(19), verticalPosition.nilReason xml_buffer, verticalPosition.xsi_nil xml_boolean, utilityFacilityReference.nilReason xml_buffer, utilityFacilityReference.gml_remoteSchema xml_buffer, utilityFacilityReference.xlink_href xml_buffer, utilityFacilityReference.xlink_role xml_buffer, utilityFacilityReference.xlink_title xml_buffer, utilityFacilityReference.owns xml_boolean, utilityFacilityReference.xsi_nil xml_boolean, governmentalServiceReference.nilReason xml_buffer, governmentalServiceReference.gml_remoteSchema xml_buffer, governmentalServiceReference.xlink_href xml_buffer, governmentalServiceReference.xlink_role xml_buffer, governmentalServiceReference.xlink_title xml_buffer,
      governmentalServiceReference.owns xml_boolean, governmentalServiceReference.xsi_nil xml_boolean
    -> FeatureJoiner [LEFT]

Bookmark: XML Reader
Utiliteitsnet (reader GML_2)
    attributes: geographicalName{}.nilReason xml_buffer, geographicalName{}.xsi_nil xml_boolean, geographicalName{}.GeographicalName.language xml_buffer, geographicalName{}.GeographicalName.language.nilReason xml_buffer, geographicalName{}.GeographicalName.language.xsi_nil xml_boolean, geographicalName{}.GeographicalName.nativeness.owns xml_boolean, geographicalName{}.GeographicalName.nativeness.nilReason xml_buffer, geographicalName{}.GeographicalName.nativeness.gml_remoteSchema xml_buffer, geographicalName{}.GeographicalName.nativeness.xlink_href xml_buffer, geographicalName{}.GeographicalName.nativeness.xlink_role xml_buffer, geographicalName{}.GeographicalName.nativeness.xlink_title xml_buffer, geographicalName{}.GeographicalName.nativeness.xsi_nil xml_boolean, geographicalName{}.GeographicalName.nameStatus.owns xml_boolean, geographicalName{}.GeographicalName.nameStatus.nilReason xml_buffer, geographicalName{}.GeographicalName.nameStatus.gml_remoteSchema xml_buffer, geographicalName{}.GeographicalName.nameStatus.xlink_href xml_buffer, geographicalName{}.GeographicalName.nameStatus.xlink_role xml_buffer, geographicalName{}.GeographicalName.nameStatus.xlink_title xml_buffer, geographicalName{}.GeographicalName.nameStatus.xsi_nil xml_boolean, geographicalName{}.GeographicalName.sourceOfName xml_buffer, geographicalName{}.GeographicalName.sourceOfName.nilReason xml_buffer, geographicalName{}.GeographicalName.sourceOfName.xsi_nil xml_boolean, geographicalName{}.GeographicalName.pronunciation.nilReason xml_buffer, geographicalName{}.GeographicalName.pronunciation.xsi_nil xml_boolean, geographicalName{}.GeographicalName.pronunciation.PronunciationOfName.pronunciationSoundLink xml_buffer, geographicalName{}.GeographicalName.pronunciation.PronunciationOfName.pronunciationSoundLink.nilReason xml_buffer, geographicalName{}.GeographicalName.pronunciation.PronunciationOfName.pronunciationSoundLink.xsi_nil xml_boolean, geographicalName{}.GeographicalName.pronunciation.PronunciationOfName.pronunciationIPA xml_buffer, geographicalName{}.GeographicalName.pronunciation.PronunciationOfName.pronunciationIPA.nilReason xml_buffer, geographicalName{}.GeographicalName.pronunciation.PronunciationOfName.pronunciationIPA.xsi_nil xml_boolean,
      geographicalName{}.GeographicalName.spelling{}.SpellingOfName.text xml_buffer, geographicalName{}.GeographicalName.spelling{}.SpellingOfName.script xml_buffer, geographicalName{}.GeographicalName.spelling{}.SpellingOfName.script.nilReason xml_buffer, geographicalName{}.GeographicalName.spelling{}.SpellingOfName.script.xsi_nil xml_boolean, geographicalName{}.GeographicalName.spelling{}.SpellingOfName.transliterationScheme xml_buffer, geographicalName{}.GeographicalName.spelling{}.SpellingOfName.transliterationScheme.nilReason xml_buffer, geographicalName{}.GeographicalName.spelling{}.SpellingOfName.transliterationScheme.xsi_nil xml_boolean, geographicalName{}.GeographicalName.grammaticalGender.owns xml_boolean, geographicalName{}.GeographicalName.grammaticalGender.nilReason xml_buffer, geographicalName{}.GeographicalName.grammaticalGender.gml_remoteSchema xml_buffer, geographicalName{}.GeographicalName.grammaticalGender.xlink_href xml_buffer, geographicalName{}.GeographicalName.grammaticalGender.xlink_role xml_buffer, geographicalName{}.GeographicalName.grammaticalGender.xlink_title xml_buffer, geographicalName{}.GeographicalName.grammaticalGender.xsi_nil xml_boolean, geographicalName{}.GeographicalName.grammaticalNumber.owns xml_boolean, geographicalName{}.GeographicalName.grammaticalNumber.nilReason xml_buffer, geographicalName{}.GeographicalName.grammaticalNumber.gml_remoteSchema xml_buffer, geographicalName{}.GeographicalName.grammaticalNumber.xlink_href xml_buffer, geographicalName{}.GeographicalName.grammaticalNumber.xlink_role xml_buffer, geographicalName{}.GeographicalName.grammaticalNumber.xlink_title xml_buffer, geographicalName{}.GeographicalName.grammaticalNumber.xsi_nil xml_boolean, elements{}.owns xml_boolean, elements{}.nilReason xml_buffer, elements{}.gml_remoteSchema xml_buffer, elements{}.xlink_href xml_buffer, elements{}.xlink_role xml_buffer, elements{}.xlink_title xml_buffer, utilityNetworkType.owns xml_boolean, utilityNetworkType.nilReason xml_buffer, utilityNetworkType.gml_remoteSchema xml_buffer,
      utilityNetworkType.xlink_href xml_buffer, utilityNetworkType.xlink_role xml_buffer, utilityNetworkType.xlink_title xml_buffer, authorityRole{}.owns xml_boolean, authorityRole{}.nilReason xml_buffer, authorityRole{}.gml_remoteSchema xml_buffer, authorityRole{}.xlink_href xml_buffer, authorityRole{}.xlink_role xml_buffer, authorityRole{}.xlink_title xml_buffer, utilityFacilityReference{}.nilReason xml_buffer, utilityFacilityReference{}.gml_remoteSchema xml_buffer, utilityFacilityReference{}.xlink_href xml_buffer, utilityFacilityReference{}.xlink_role xml_buffer, utilityFacilityReference{}.xlink_title xml_buffer, utilityFacilityReference{}.owns xml_boolean, utilityFacilityReference{}.xsi_nil xml_boolean, disclaimer{}.gco_nilReason xml_buffer, disclaimer{}.xsi_nil xml_boolean, disclaimer{}.CI_DateTypeCode xml_buffer, disclaimer{}.CI_DateTypeCode.codeList xml_buffer, disclaimer{}.CI_DateTypeCode.codeListValue xml_buffer, disclaimer{}.CI_DateTypeCode.codeSpace xml_buffer, disclaimer{}.CI_OnLineFunctionCode xml_buffer, disclaimer{}.CI_OnLineFunctionCode.codeList xml_buffer, disclaimer{}.CI_OnLineFunctionCode.codeListValue xml_buffer, disclaimer{}.CI_OnLineFunctionCode.codeSpace xml_buffer, disclaimer{}.CI_PresentationFormCode xml_buffer, disclaimer{}.CI_PresentationFormCode.codeList xml_buffer, disclaimer{}.CI_PresentationFormCode.codeListValue xml_buffer, disclaimer{}.CI_PresentationFormCode.codeSpace xml_buffer,
      disclaimer{}.CI_RoleCode xml_buffer, disclaimer{}.CI_RoleCode.codeList xml_buffer, disclaimer{}.CI_RoleCode.codeListValue xml_buffer, disclaimer{}.CI_RoleCode.codeSpace xml_buffer, disclaimer{}.Country xml_buffer, disclaimer{}.Country.codeList xml_buffer, disclaimer{}.Country.codeListValue xml_buffer, disclaimer{}.Country.codeSpace xml_buffer, disclaimer{}.DQ_EvaluationMethodTypeCode xml_buffer, disclaimer{}.DQ_EvaluationMethodTypeCode.codeList xml_buffer, disclaimer{}.DQ_EvaluationMethodTypeCode.codeListValue xml_buffer, disclaimer{}.DQ_EvaluationMethodTypeCode.codeSpace xml_buffer, disclaimer{}.DS_AssociationTypeCode xml_buffer, disclaimer{}.DS_AssociationTypeCode.codeList xml_buffer, disclaimer{}.DS_AssociationTypeCode.codeListValue xml_buffer, disclaimer{}.DS_AssociationTypeCode.codeSpace xml_buffer, disclaimer{}.DS_InitiativeTypeCode xml_buffer, disclaimer{}.DS_InitiativeTypeCode.codeList xml_buffer, disclaimer{}.DS_InitiativeTypeCode.codeListValue xml_buffer, disclaimer{}.DS_InitiativeTypeCode.codeSpace xml_buffer, disclaimer{}.LanguageCode xml_buffer, disclaimer{}.LanguageCode.codeList xml_buffer, disclaimer{}.LanguageCode.codeListValue xml_buffer, disclaimer{}.LanguageCode.codeSpace xml_buffer, disclaimer{}.LocalisedCharacterString xml_buffer, disclaimer{}.LocalisedCharacterString.id xml_buffer, disclaimer{}.LocalisedCharacterString.locale xml_buffer, disclaimer{}.MD_CellGeometryCode xml_buffer, disclaimer{}.MD_CellGeometryCode.codeList xml_buffer, disclaimer{}.MD_CellGeometryCode.codeListValue xml_buffer,
      disclaimer{}.MD_CellGeometryCode.codeSpace xml_buffer, disclaimer{}.MD_CharacterSetCode xml_buffer, disclaimer{}.MD_CharacterSetCode.codeList xml_buffer, disclaimer{}.MD_CharacterSetCode.codeListValue xml_buffer, disclaimer{}.MD_CharacterSetCode.codeSpace xml_buffer, disclaimer{}.MD_ClassificationCode xml_buffer, disclaimer{}.MD_ClassificationCode.codeList xml_buffer, disclaimer{}.MD_ClassificationCode.codeListValue xml_buffer, disclaimer{}.MD_ClassificationCode.codeSpace xml_buffer, disclaimer{}.MD_CoverageContentTypeCode xml_buffer, disclaimer{}.MD_CoverageContentTypeCode.codeList xml_buffer, disclaimer{}.MD_CoverageContentTypeCode.codeListValue xml_buffer, disclaimer{}.MD_CoverageContentTypeCode.codeSpace xml_buffer, disclaimer{}.MD_DatatypeCode xml_buffer, disclaimer{}.MD_DatatypeCode.codeList xml_buffer, disclaimer{}.MD_DatatypeCode.codeListValue xml_buffer, disclaimer{}.MD_DatatypeCode.codeSpace xml_buffer, disclaimer{}.MD_DimensionNameTypeCode xml_buffer, disclaimer{}.MD_DimensionNameTypeCode.codeList xml_buffer, disclaimer{}.MD_DimensionNameTypeCode.codeListValue xml_buffer, disclaimer{}.MD_DimensionNameTypeCode.codeSpace xml_buffer, disclaimer{}.MD_DistributionUnits xml_buffer, disclaimer{}.MD_DistributionUnits.codeList xml_buffer, disclaimer{}.MD_DistributionUnits.codeListValue xml_buffer, disclaimer{}.MD_DistributionUnits.codeSpace xml_buffer, disclaimer{}.MD_GeometricObjectTypeCode xml_buffer, disclaimer{}.MD_GeometricObjectTypeCode.codeList xml_buffer, disclaimer{}.MD_GeometricObjectTypeCode.codeListValue xml_buffer, disclaimer{}.MD_GeometricObjectTypeCode.codeSpace xml_buffer, disclaimer{}.MD_ImagingConditionCode xml_buffer,
      disclaimer{}.MD_ImagingConditionCode.codeList xml_buffer, disclaimer{}.MD_ImagingConditionCode.codeListValue xml_buffer, disclaimer{}.MD_ImagingConditionCode.codeSpace xml_buffer, disclaimer{}.MD_KeywordTypeCode xml_buffer, disclaimer{}.MD_KeywordTypeCode.codeList xml_buffer, disclaimer{}.MD_KeywordTypeCode.codeListValue xml_buffer, disclaimer{}.MD_KeywordTypeCode.codeSpace xml_buffer, disclaimer{}.MD_MaintenanceFrequencyCode xml_buffer, disclaimer{}.MD_MaintenanceFrequencyCode.codeList xml_buffer, disclaimer{}.MD_MaintenanceFrequencyCode.codeListValue xml_buffer, disclaimer{}.MD_MaintenanceFrequencyCode.codeSpace xml_buffer, disclaimer{}.MD_MediumFormatCode xml_buffer, disclaimer{}.MD_MediumFormatCode.codeList xml_buffer, disclaimer{}.MD_MediumFormatCode.codeListValue xml_buffer, disclaimer{}.MD_MediumFormatCode.codeSpace xml_buffer, disclaimer{}.MD_MediumNameCode xml_buffer, disclaimer{}.MD_MediumNameCode.codeList xml_buffer, disclaimer{}.MD_MediumNameCode.codeListValue xml_buffer, disclaimer{}.MD_MediumNameCode.codeSpace xml_buffer, disclaimer{}.MD_ObligationCode xml_char(11), disclaimer{}.MD_PixelOrientationCode xml_char(10), disclaimer{}.MD_ProgressCode xml_buffer, disclaimer{}.MD_ProgressCode.codeList xml_buffer, disclaimer{}.MD_ProgressCode.codeListValue xml_buffer, disclaimer{}.MD_ProgressCode.codeSpace xml_buffer, disclaimer{}.MD_RestrictionCode xml_buffer, disclaimer{}.MD_RestrictionCode.codeList xml_buffer, disclaimer{}.MD_RestrictionCode.codeListValue xml_buffer, disclaimer{}.MD_RestrictionCode.codeSpace xml_buffer, disclaimer{}.MD_ScopeCode xml_buffer,
      disclaimer{}.MD_ScopeCode.codeList xml_buffer, disclaimer{}.MD_ScopeCode.codeListValue xml_buffer, disclaimer{}.MD_ScopeCode.codeSpace xml_buffer, disclaimer{}.MD_SpatialRepresentationTypeCode xml_buffer, disclaimer{}.MD_SpatialRepresentationTypeCode.codeList xml_buffer, disclaimer{}.MD_SpatialRepresentationTypeCode.codeListValue xml_buffer, disclaimer{}.MD_SpatialRepresentationTypeCode.codeSpace xml_buffer, disclaimer{}.MD_TopicCategoryCode xml_char(32), disclaimer{}.MD_TopologyLevelCode xml_buffer, disclaimer{}.MD_TopologyLevelCode.codeList xml_buffer, disclaimer{}.MD_TopologyLevelCode.codeListValue xml_buffer, disclaimer{}.MD_TopologyLevelCode.codeSpace xml_buffer, disclaimer{}.CharacterString xml_buffer, disclaimer{}.PT_FreeText.id xml_buffer, disclaimer{}.PT_FreeText.uuid xml_buffer, disclaimer{}.PT_FreeText.textGroup{}.gco_nilReason xml_buffer, disclaimer{}.PT_FreeText.textGroup{}.uuidref xml_buffer, disclaimer{}.PT_FreeText.textGroup{}.xlink_href xml_buffer, disclaimer{}.PT_FreeText.textGroup{}.xlink_role xml_buffer, disclaimer{}.PT_FreeText.textGroup{}.xlink_title xml_buffer, disclaimer{}.PT_FreeText.textGroup{}.LocalisedCharacterString xml_buffer, disclaimer{}.PT_FreeText.textGroup{}.LocalisedCharacterString.id xml_buffer, disclaimer{}.PT_FreeText.textGroup{}.LocalisedCharacterString.locale xml_buffer, networks{}.owns xml_boolean, networks{}.nilReason xml_buffer, networks{}.gml_remoteSchema xml_buffer, networks{}.xlink_href xml_buffer, networks{}.xlink_role xml_buffer, networks{}.xlink_title xml_buffer, networks{}.xsi_nil xml_boolean,
      identificatie.NEN3610ID.namespace xml_buffer, identificatie.NEN3610ID.lokaalID xml_buffer, identificatie.NEN3610ID.versie xml_buffer, beginLifespanVersion xml_datetime, endLifespanVersion xml_datetime, label xml_buffer, omschrijving xml_buffer, thema.owns xml_boolean, thema.nilReason xml_buffer, thema.gml_remoteSchema xml_buffer, thema.xlink_href xml_buffer, thema.xlink_role xml_buffer, thema.xlink_title xml_buffer, standaardDieptelegging xml_real64, standaardDieptelegging.uom xml_buffer, heeftExtraInformatie{}.owns xml_boolean, heeftExtraInformatie{}.nilReason xml_buffer, heeftExtraInformatie{}.gml_remoteSchema xml_buffer, heeftExtraInformatie{}.xlink_href xml_buffer, heeftExtraInformatie{}.xlink_role xml_buffer, heeftExtraInformatie{}.xlink_title xml_buffer
    -> AttributeCreator__inspire_thema_id

Bookmark: DGN Writer
UtilityLink (writer DGNV8_1)
    attributes: thema char(200), netbeheerder char(200), layerName char(200), inspireId.Identifier.localId string, inNetwork{}.xlink_href string, endNode.gml_remoteSchema string, startNode.gml_remoteSchema string, gml_parent_id string, gml_parent_property string, gml_id string, inspire_thema_id char(200), thema.xlink_href string, _thema{} char(200), thema_color char(200)

Bookmark: DXF Writer
Layer1 (writer ACAD_1)
    attributes: thema char(200), netbeheerder char(200), layerName char(200), inspireId_Identifier_localId string, inNetwork{}_xlink_href string, endNode_gml_remoteSchema string, startNode_gml_remoteSchema string, gml_parent_id string, gml_parent_property string, gml_id string, inspire_thema_id char(200), thema_xlink_href string, _thema{} char(200), thema_color char(200)

Bookmark: DXF Total Writer
UtilityLink (writer ACAD_2)
    attributes: thema string, netbeheerder string, layerName char(200), inspireId_Identifier_localId string, inNetwork{}_xlink_href string, endNode_gml_remoteSchema string, startNode_gml_remoteSchema string, gml_parent_id string, gml_parent_property string, gml_id string, inspire_thema_id char(200), thema_xlink_href string, _thema{} char(200), thema_color char(200)
